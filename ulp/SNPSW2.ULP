/*  SNPSW2.ULP
 *  This EAGLE User Language Program produces a script
 *  file that can be used to snap the wire ends #2
 *  of the current schematic to the current grid.
 *  creates snap.scr in the working directory, which
 *  does the actual moving (not possible in ULP (yet?))
 *  Iterate with SNPSP.ULP, SNPSJ.ULP and SNPSW1.ULP
 */

real GridDist; // in Mil

real snap(int n)  // returns next grid point
{
  return round(u2mil(n) / GridDist) * GridDist;
}

real gridDist2Mil(real gridDist, int gridUnit) //
{
  switch (gridUnit) {
    case GRID_UNIT_MIC : return u2mil(int(gridDist*10.0));break;
    case GRID_UNIT_MM  : return u2mil(int(gridDist*10000.0));break;
    case GRID_UNIT_MIL : return gridDist;break;
    case GRID_UNIT_INCH: return gridDist*1000.0;break;
    default : exit(-1); }
}

output("snap.scr") {
  schematic(SCH) {
    GridDist = gridDist2Mil(SCH.grid.distance, SCH.grid.unit);
    printf("GRID MIL %f;\n", 1.0);
    SCH.sheets(SH) {
      SH.nets(N) {
        N.segments(SEG) {
          SEG.wires(W) {
            printf("MOVE (%f %f) (%f %f);\n",
                   u2mil(W.x2), u2mil(W.y2), snap(W.x2), snap(W.y2));
          }
        }
      }
    }
  }
  printf("GRID LAST;\n");
}
